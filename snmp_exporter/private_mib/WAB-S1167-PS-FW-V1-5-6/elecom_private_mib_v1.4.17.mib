ELECOM-WAB-AP-CONFIGURATION DEFINITIONS ::= BEGIN

	IMPORTS
		enterprises
			FROM RFC1155-SMI
		mgmt, NetworkAddress, IpAddress, Counter, Gauge, TimeTicks
			FROM RFC1155-SMI
		OBJECT-TYPE
			FROM RFC-1212
		DisplayString
			FROM RFC1213-MIB;

elecom OBJECT IDENTIFIER ::= { enterprises 41868 }



apIpSetting		OBJECT IDENTIFIER ::= { elecom 10 }
apIpConfig		OBJECT IDENTIFIER ::= { elecom 11 }
apMacFilter		OBJECT IDENTIFIER ::= { elecom 13 }
apManLogin		OBJECT IDENTIFIER ::= { elecom 14 }
apConfig		OBJECT IDENTIFIER ::= { elecom 15 }
apFW			OBJECT IDENTIFIER ::= { elecom 16 }
apUtil			OBJECT IDENTIFIER ::= { elecom 17 }
apSyslog		OBJECT IDENTIFIER ::= { elecom 18 }
apBoot			OBJECT IDENTIFIER ::= { elecom 19 }
apNTP           OBJECT IDENTIFIER ::= { elecom 20 }
apWPS           OBJECT IDENTIFIER ::= { elecom 21 }


-- ========================================
-- Basic Function
-- ========================================
wabIpSetting		OBJECT IDENTIFIER ::= { apIpSetting 1 }
wabIpConfigulation OBJECT-TYPE
	SYNTAX	INTEGER {
		dhcp_Lease(1),
		static_Ip(2)
	}
	ACCESS	read-write
	STATUS	mandatory
	DESCRIPTION
		"This OID Configures IP address of the Access Point.
		  [1] get IP address from DHCP Lease
		  [2] assign static IP address
		 Note : When you configure the OID as 2, you need to configre following related OID.
		    wabIpAddress
		    wabSubnetMask
		    wabGateWay
		"
	::= { wabIpSetting 1 }

wabIpConfig		OBJECT IDENTIFIER ::= { apIpConfig 1 }

wabIpAddress OBJECT-TYPE
	SYNTAX	IpAddress
	ACCESS	read-write
	STATUS	mandatory
	DESCRIPTION
		"This OID configure_indicate Current IP address of the Access Point.
		 Note : This OID is related with following OID.
			wabIpConfig : configure as static IP"
	::= { wabIpConfig 1 }

wabSubnetMask OBJECT-TYPE
	SYNTAX	IpAddress
	ACCESS	read-write
	STATUS	mandatory
	DESCRIPTION
		"This OID configure_indicate Current subnetmask of the Access Point.
		 Note : This OID is related with following OID.
			wabIpConfig : configure as static IP
		"
	::= { wabIpConfig 2 }

wabGateWay OBJECT-TYPE
	SYNTAX	IpAddress
	ACCESS	read-write
	STATUS	mandatory
	DESCRIPTION
		"This OID configure_indicate Current address of default gateway for the Access Point.
		 Note : This OID is related with following OID.
			wabIpConfig : configure as static IP
		"
	::= { wabIpConfig 3 }

-- ========================================
-- RADIUS
-- ========================================

    RADIUSTable   OBJECT-TYPE
      SYNTAX  SEQUENCE OF RADIUSEntry
      ACCESS  not-accessible
      STATUS  current
      DESCRIPTION
              "Table of RADIUS servers."
      ::= { elecom 12 }

    ApWABRADIUSEntry OBJECT-TYPE
        SYNTAX  RADIUSEntry
        ACCESS  not-accessible
        STATUS  current
        DESCRIPTION
            "This OID configures the setting of RADIUS server."
        INDEX   { PrimaryRADIUSServer }
        ::= { RADIUSTable 1 }

    RADIUSEntry ::=
      SEQUENCE {
          PrimaryRADIUSServer
              OCTET STRING,
          PrimaryAuthPort
              INTEGER,
          PrimarySharedSecret
              OCTET STRING,
          PrimarySessionTimeout
              INTEGER,
          PrimaryAccounting
              INTEGER,
          PrimaryAccountingPort
              INTEGER,
          SeccondaryRADIUSServer
              OCTET STRING,
          SeccondaryAuthPort
              INTEGER,
          SeccondarySharedSecret
              OCTET STRING,
          SeccondarySessionTimeout
              INTEGER,
          SeccondaryAccounting
              INTEGER,
          SeccondaryAccountingPort
              INTEGER
      }

    PrimaryRADIUSServer OBJECT-TYPE
        SYNTAX  OCTET STRING
        ACCESS  read-write
        STATUS  mandatory
        DESCRIPTION
            "This OID configures IP/hostname of Primary RADIUS Server"
        ::= { ApWABRADIUSEntry 1 }

    PrimaryAuthPort OBJECT-TYPE
        SYNTAX  INTEGER {
            1~65535
        }
        ACCESS  read-write
        DESCRIPTION
            "This OID configures Authentication Port of Primary RADIUS Server"
        ::= { ApWABRADIUSEntry 2 }

    PrimarySharedSecret OBJECT-TYPE
        SYNTAX  OCTET STRING
        ACCESS  read-write
        STATUS  mandatory
        DESCRIPTION
            "This OID configures Shared Secret of Primary RADIUS Server"
        ::= { ApWABRADIUSEntry 3 }

    PrimarySessionTimeout OBJECT-TYPE
        SYNTAX  INTEGER {
            0~86400
        }
        ACCESS  read-write
        DESCRIPTION
            "This OID configures Session Timeout of Primary RADIUS Server"
        ::= { ApWABRADIUSEntry 4 }

    PrimaryAccounting OBJECT-TYPE
        SYNTAX  INTEGER {
            Enable(1),
            Disable(2)
        }
        ACCESS  read-write
        DESCRIPTION
            "This OID configures Enable/Disable of Accounting of Primary RADIUS Server"
        ::= { ApWABRADIUSEntry 5 }

    PrimaryAccountingPort OBJECT-TYPE
        SYNTAX  INTEGER {
            1~65535
        }
        ACCESS  read-write
        DESCRIPTION
            "This OID configures Authentication Port of Primary RADIUS Server"
        ::= { ApWABRADIUSEntry 6 }

    SeccondaryRADIUSServer OBJECT-TYPE
        SYNTAX  OCTET STRING
        ACCESS  read-write
        STATUS  mandatory
        DESCRIPTION
            "This OID configures IP/hostname of Seccondary RADIUS Server"
        ::= { ApWABRADIUSEntry 7 }

    SeccondaryAuthPort OBJECT-TYPE
        SYNTAX  INTEGER {
            1~65535
        }
        ACCESS  read-write
        DESCRIPTION
            "This OID configures Authentication Port of Seccondary RADIUS Server"
        ::= { ApWABRADIUSEntry 8 }

    SeccondarySharedSecret OBJECT-TYPE
        SYNTAX  OCTET STRING
        ACCESS  read-write
        STATUS  mandatory
        DESCRIPTION
            "This OID configures Shared Secret of Seccondary RADIUS Server"
        ::= { ApWABRADIUSEntry 9 }

    SeccondarySessionTimeout OBJECT-TYPE
        SYNTAX  INTEGER {
            0~86400
        }
        ACCESS  read-write
        DESCRIPTION
            "This OID configures Session Timeout of Seccondary RADIUS Server"
        ::= { ApWABRADIUSEntry 10 }

    SeccondaryAccounting OBJECT-TYPE
        SYNTAX  INTEGER {
            Enable(1),
            Disable(2)
        }
        ACCESS  read-write
        DESCRIPTION
            "This OID configures Enable/Disable of Accounting of Seccondary RADIUS Server"
        ::= { ApWABRADIUSEntry 11 }

    SeccondaryAccountingPort OBJECT-TYPE
        SYNTAX  INTEGER {
            1~65535
        }
        ACCESS  read-write
        DESCRIPTION
            "This OID configures Authentication Port of Seccondary RADIUS Server"
        ::= { ApWABRADIUSEntry 12 }

-- ========================================
-- MacAddress Filter
-- ========================================
elecomApMacFilter				OBJECT IDENTIFIER ::= { apMacFilter 1 }

elecomApMacFilterList			OBJECT IDENTIFIER ::= { elecomApMacFilter 1 }
elecomWABApMacFilterList		OBJECT IDENTIFIER ::= { elecomApMacFilterList 4 }

	eleApWABMacFilterList OBJECT-TYPE
	 	SYNTAX	SEQUENCE OF MacFilterEntry
		ACCESS	not-accessible
	 	STATUS	mandatory
	 	DESCRIPTION
		"This OID indicate the list of the MAC address fiter of the Access Point.
	 		 the maximum number of the register address is 4096 "
	 	::= { elecomWABApMacFilterList 0 }

		eleApWABMacFilterTable OBJECT-TYPE
			SYNTAX	MacFilterEntry
			ACCESS	not-accessible
			STATUS	mandatory
			DESCRIPTION
				""
			INDEX  { macAddressFilter }
			::= { eleApWABMacFilterList 0 }

		MacFilterEntry ::=
		  SEQUENCE {
		      macAddressFilter
		          OCTET STRING
		  }

		macAddressFilter OBJECT-TYPE
			SYNTAX  OCTET STRING
			ACCESS  read-only
			STATUS  mandatory
			DESCRIPTION
				"This OID is MAC address that was register to the MAC address filter."
			::= { eleApWABMacFilterTable 0 }

elecomApMacFilterAdd				OBJECT IDENTIFIER ::= { elecomApMacFilter 2 }
elecomWABApMacFilterAdd				OBJECT IDENTIFIER ::= { elecomApMacFilterAdd 4 }
elecomWABApMacFilterAdd_Opt1		OBJECT IDENTIFIER ::= { elecomWABApMacFilterAdd 0 }
elecomWABApMacFilterAdd_Opt2		OBJECT IDENTIFIER ::= { elecomWABApMacFilterAdd_Opt1 0 }
elecomWABApMacFilterAdd_Opt3		OBJECT IDENTIFIER ::= { elecomWABApMacFilterAdd_Opt2 0 }
eleApWABMacFilterListAdd OBJECT-TYPE
	SYNTAX	IpAddress
	ACCESS	write-only
	STATUS	mandatory
	DESCRIPTION
		"This OID add the MAC address to the list of the MAC address fiter of the Access Point.
		 the format is XX:XX:XX:XX:XX:XX
		"
	::= { elecomWABApMacFilterAdd_Opt3 1 }



elecomApMacFilterDelete					OBJECT IDENTIFIER ::= { elecomApMacFilter 3 }
elecomWABApMacFilterDelete				OBJECT IDENTIFIER ::= { elecomApMacFilterDelete 4 }
elecomWABApMacFilterDelete_opt1			OBJECT IDENTIFIER ::= { elecomWABApMacFilterDelete 0 }
elecomWABApMacFilterDelete_opt2			OBJECT IDENTIFIER ::= { elecomWABApMacFilterDelete_opt1 0 }
elecomWABApMacFilterDelete_opt3			OBJECT IDENTIFIER ::= { elecomWABApMacFilterDelete_opt2 0 }

eleApWABMacFilterDelete OBJECT-TYPE
	SYNTAX	IpAddress
	ACCESS	write-only
	STATUS	mandatory
	DESCRIPTION
		"This OID delete the MAC address from the list of the MAC address fiter of the Access Point.
		 To delete the Mac, write 1 to the OID.
		"
	::= { elecomWABApMacFilterDelete_opt3 0 }

elecomApMacFilterDeleteAll		OBJECT IDENTIFIER ::= { elecomApMacFilter 4 }

eleApWABMacFilterDeleteAll		OBJECT-TYPE
	SYNTAX	IpAddress
	ACCESS	write-only
	STATUS	mandatory
	DESCRIPTION
		"This OID delete all of the MAC address from the list of the MAC address fiter of the Access Point.
		 To delete all of the MAC addressthe Mac, write 1 to the OID.
		"
	::= { elecomApMacFilterDeleteAll 4 }

-- ========================================
-- Management Login
-- ========================================
wabManLogin			OBJECT IDENTIFIER ::= { apManLogin 1 }
eleWabManName OBJECT-TYPE
	SYNTAX	OCTET STRING
	ACCESS	read-write
	STATUS	mandatory
	DESCRIPTION
		"This OID Configure_indicate Manaemaent user name of the Access Point.
		 Note : This OID is related with following OID.
			eleWabManPassword : Password for Manaemaent user
			"
	::= { wabManLogin 1 }

eleWabManPassword OBJECT-TYPE
	SYNTAX	OCTET STRING
	ACCESS	write-only
	STATUS	mandatory
	DESCRIPTION
		"This OID configure Password for Manaemaent user of the Access Point.
		 Note : This OID is related with following OID.
			eleWabManName Manaemaent user name
		 " 
	::= { wabManLogin 2 }

-- ========================================
-- Configuration
-- ========================================
elecomApConfig		OBJECT IDENTIFIER ::= { apConfig 1 }
wabConfigBackup		OBJECT IDENTIFIER ::= { elecomApConfig 1 }
wabConfigBackup_1	OBJECT IDENTIFIER ::= { wabConfigBackup 0 }
wabConfigBackup_2	OBJECT IDENTIFIER ::= { wabConfigBackup_1 0 }
eleApWABConfigBackup OBJECT-TYPE
	SYNTAX	INTEGER
	ACCESS	write-only
	STATUS	mandatory
	DESCRIPTION
		"This OID backups configuration of the Access Point.
		 To save the configuration, exec the tftp server on SNMP client before write 1 to the OID. "
	::= { wabConfigBackup_2 0 }

wabConfigUpload		OBJECT IDENTIFIER ::= { elecomApConfig 2 }
wabConfigUpload_1	OBJECT IDENTIFIER ::= { wabConfigUpload 0 }
wabConfigUpload_2	OBJECT IDENTIFIER ::= { wabConfigUpload_1 0 }
eleApWABConfigUpdate OBJECT-TYPE
	SYNTAX	INTEGER
	ACCESS	write-only
	STATUS	mandatory
	DESCRIPTION
		"This OID upload configuration of the Access Point.
		 To upload the configuration, exec the tftp server on SNMP client before write 1 to the OID. "
	::= { wabConfigUpload_2 0 }

-- ========================================
-- FW update
-- ========================================

elecomApFW		OBJECT IDENTIFIER ::= { apFW 1 }
wabFWUpdate		OBJECT IDENTIFIER ::= { elecomApFW 1 }
wabFWUpdate_1	OBJECT IDENTIFIER ::= { wabFWUpdate 0 }
wabFWUpdate_2	OBJECT IDENTIFIER ::= { wabFWUpdate_1 0 }
eleApWABFWUpdate OBJECT-TYPE
	SYNTAX	INTEGER
	ACCESS	write-only
	STATUS	mandatory
	DESCRIPTION
		"This OID updates firmware of the Access Point.
		 To update the firmware, exec the tftp server on SNMP client before write 1 to the OID. "
	::= { wabFWUpdate_2 0 }


-- ========================================
-- Util
-- ========================================

elecomApUtil	OBJECT IDENTIFIER ::= { apUtil 1 }
wabImHere		OBJECT IDENTIFIER ::= { elecomApUtil 1 }
eleApWABImHere OBJECT-TYPE
	SYNTAX	INTEGER
	ACCESS	read-write
	STATUS	mandatory
	DESCRIPTION
		"This OID beep the buzzer of the Access Point.
		 write the number of seconds to beep.
		 "
	::= { wabImHere 0 }


-- ========================================
-- Syslog
-- ========================================

elecomApSyslog			OBJECT IDENTIFIER ::= { apSyslog 1 }
wabSyslog		OBJECT IDENTIFIER ::= { elecomApSyslog 1 }
eleApWABSyslog OBJECT-TYPE
	SYNTAX	INTEGER
	ACCESS	read-write
	STATUS	mandatory
	DESCRIPTION
		"This OID configure the IP address of the syslog server."
	::= { wabSyslog 0 }


-- ========================================
-- Reboot
-- ========================================

elecomApBoot			OBJECT IDENTIFIER ::= { apBoot 1 }
wabBoot		OBJECT IDENTIFIER ::= { elecomApBoot 1 }
eleApWABBoot OBJECT-TYPE
	SYNTAX	INTEGER
	ACCESS	write-only
	STATUS	mandatory
	DESCRIPTION
		"This OID make reboot the Access Point.
		 to reboot the Access point, write 1 to the OID."
	::= { wabBoot 0 }

-- ========================================
-- NTP
-- ========================================
wabapNTP         OBJECT IDENTIFIER ::= { apNTP 1 }
eleWabapNTPEnable OBJECT-TYPE
    SYNTAX  INTEGER {
        Enable(1),
        Disable(2)
    }
    ACCESS  read-write
    STATUS  mandatory
    DESCRIPTION
        "This OID configres the Enable _ Disaable NTP Time Server."
    ::= { wabapNTP 1 }

eleWabNTPServer OBJECT-TYPE
    SYNTAX  OCTET STRING
    ACCESS  read-write
    STATUS  mandatory
    DESCRIPTION
        "This OID configure NTP Time Server."
    ::= { wabapNTP 2 }

-- ========================================
-- WPS
-- ========================================
wabapWPS         OBJECT IDENTIFIER ::= { apWPS 1 }
eleWabapNTPEnable OBJECT-TYPE
    SYNTAX  INTEGER {
        Enable(1),
        Disable(2)
    }
    ACCESS  read-write
    STATUS  mandatory
    DESCRIPTION
        "This OID configres the Enable _ Disaable WPS."
    ::= { wabapWPS 1 }


-- ========================================
-- Guest Network
-- ========================================

    GuestNetworkTable   OBJECT-TYPE
      SYNTAX  SEQUENCE OF GuestNetworkEntry
      ACCESS  not-accessible
      STATUS  current
      DESCRIPTION
              "Table of Guest Network."
      ::= { elecom 22 }

    ApWABGuestNetworkEntry OBJECT-TYPE
        SYNTAX  GuestNetworkEntry
        ACCESS  not-accessible
        STATUS  current
        DESCRIPTION
            "This OID configures the setting of Guest Network."
        INDEX   { GuestNetworkEnable }
        ::= { GuestNetworkTable 1 }

    GuestNetworkEntry ::=
      SEQUENCE {
          GuestNetworkEnable
              INTEGER,
          WirelessBand
              INTEGER,
          SSIDSelect
              INTEGER,
          SSIDName
              OCTET STRING,
          DHCPIPAddress
              OCTET STRING,
          DHCPSubnetMask
              OCTET STRING,
          DHCPLeaseTime
              INTEGER,
          DHCPStartingIPAddress
              OCTET STRING,
          DHCPEndingIPAddress
              OCTET STRING,
          GuestConnectableTime
              INTEGER,
          ConnectionRestrictionTime
              INTEGER,
          GuestAuthType
              INTEGER,
          SenderEmail
              OCTET STRING,
          SMTPServerAddress
              OCTET STRING,
          SMTPServerPort
              INTEGER,
          SMTPAuthType
              INTEGER,
          SMTPAccount
              OCTET STRING,
          SMTPPassword
              OCTET STRING,
          TrafficShaping
              INTEGER,
          LimitedRate
              INTEGER,
          AdminDeviceMAC
              OCTET STRING
      }

    GuestNetworkEnable OBJECT-TYPE
        SYNTAX  INTEGER {
            Enable(1),
            Disable(2)
        }
        ACCESS  read-write
        DESCRIPTION
            "This OID configures Enable/Disable of Guest Network"
        ::= { ApWABGuestNetworkEntry 1 }

    WirelessBand OBJECT-TYPE
        SYNTAX  INTEGER {
            2.4GHz(1),
            5GHz(2)
        }
        ACCESS  read-write
        DESCRIPTION
            "This OID configures wireless band of Guest Network"
        ::= { ApWABGuestNetworkEntry 2 }

    SSIDSelect OBJECT-TYPE
        SYNTAX  INTEGER {
            1~16
        }
        ACCESS  read-write
        STATUS  mandatory
        DESCRIPTION
            "This OID configures the selected SSID of Guest Network"
        ::= { ApWABGuestNetworkEntry 3 }

    SSIDName OBJECT-TYPE
        SYNTAX  OCTET STRING
        ACCESS  read-write
        DESCRIPTION
            "This OID configures the name of selected SSID for Guest Network"
        ::= { ApWABGuestNetworkEntry 4 }

    DHCPIPAddress OBJECT-TYPE
        SYNTAX  OCTET STRING
        ACCESS  read-write
        DESCRIPTION
            "This OID configures DHCP IP Address for Guest Network"
        ::= { ApWABGuestNetworkEntry 5 }

    DHCPSubnetMask OBJECT-TYPE
        SYNTAX  OCTET STRING
        ACCESS  read-write
        DESCRIPTION
            "This OID configures DHCP Subnet Mask for Guest Network"
        ::= { ApWABGuestNetworkEntry 6 }

    DHCPLeaseTime OBJECT-TYPE
        SYNTAX  INTEGER {
            1(0.5 hr), 2(1 hr), 3(2 hrs), 4(0.5 day), 5(1 day), 6(2 day), 7(1 week), 8(2 weeks), 9(forever)
        }
        ACCESS  read-write
        DESCRIPTION
            "This OID configures DHCP Lease Timefor Guest Network"
        ::= { ApWABGuestNetworkEntry 7 }

    DHCPStartingIPAddress OBJECT-TYPE
        SYNTAX  OCTET STRING
        ACCESS  read-write
        DESCRIPTION
            "This OID configures DHCP Starting IP Address for Guest Network"
        ::= { ApWABGuestNetworkEntry 8 }

    DHCPEndingIPAddress OBJECT-TYPE
        SYNTAX  OCTET STRING
        ACCESS  read-write
        DESCRIPTION
            "This OID configures DHCP Ending IP Address for Guest Network"
        ::= { ApWABGuestNetworkEntry 9 }

    GuestConnectableTime OBJECT-TYPE
        SYNTAX  INTEGER {
            1~24
        }
        ACCESS  read-write
        DESCRIPTION
            "This OID configures Connectable Time of Guest Network"
        ::= { ApWABGuestNetworkEntry 10 }

    ConnectionRestrictionTime OBJECT-TYPE
        SYNTAX  INTEGER {
            12~24
        }
        ACCESS  read-write
        DESCRIPTION
            "This OID configures Connection Restriction of Guest Network"
        ::= { ApWABGuestNetworkEntry 11 }

    GuestAuthType OBJECT-TYPE
        SYNTAX  INTEGER {
            AuthScreen(1),
            E-mailAuth(2),
            Disable(3)
        }
        ACCESS  read-write
        DESCRIPTION
            "This OID configures Authentication Type of Guest Network"
        ::= { ApWABGuestNetworkEntry 12 }

    SenderEmail OBJECT-TYPE
        SYNTAX  OCTET STRING
        ACCESS  read-write
        DESCRIPTION
            "This OID configures Sender email for Email Authentication"
        ::= { ApWABGuestNetworkEntry 13 }

    SMTPServerAddress OBJECT-TYPE
        SYNTAX  OCTET STRING
        ACCESS  read-write
        DESCRIPTION
            "This OID configures SMTP Server Address for Email Authentication"
        ::= { ApWABGuestNetworkEntry 14 }

    SMTPServerPort OBJECT-TYPE
        SYNTAX  INTEGER {
            1~65535
        }
        ACCESS  read-write
        DESCRIPTION
            "This OID configures SMTP Server Port for Email Authentication"
        ::= { ApWABGuestNetworkEntry 15 }

    SMTPAuthType OBJECT-TYPE
        SYNTAX  INTEGER {
            Disable(1),
            SSL(2),
            TLS(3)
        }
        ACCESS  read-write
        DESCRIPTION
            "This OID configures SMTP Auth Type for Email Authentication"
        ::= { ApWABGuestNetworkEntry 16 }

    SMTPAccount OBJECT-TYPE
        SYNTAX  OCTET STRING
        ACCESS  read-write
        DESCRIPTION
            "This OID configures SMTP Account for Email Authentication"
        ::= { ApWABGuestNetworkEntry 17 }

    SMTPPassword OBJECT-TYPE
        SYNTAX  OCTET STRING
        ACCESS  read-only
        DESCRIPTION
            "This OID configures SMTP Password for Email Authentication"
        ::= { ApWABGuestNetworkEntry 18 }

    TrafficShaping OBJECT-TYPE
        SYNTAX  INTEGER {
            Enable(1),
            Disable(2)
        }
        ACCESS  read-write
        DESCRIPTION
            "This OID configures Enable/Disable Traffic Shaping"
        ::= { ApWABGuestNetworkEntry 19 }

    LimitedRate OBJECT-TYPE
        SYNTAX  INTEGER {
            100~43000
        }
        ACCESS  read-write
        DESCRIPTION
            "This OID configures Limited Rate of Traffic Shaping"
        ::= { ApWABGuestNetworkEntry 20 }

    AdminDeviceMAC OBJECT-TYPE
        SYNTAX  OCTET STRING
        ACCESS  read-write
        DESCRIPTION
            "This OID configures AdminDeviceMAC of Guest Network"
        ::= { ApWABGuestNetworkEntry 21 }


-- ========================================
-- Emergency Mode
-- ========================================

    EmergencyModeTable   OBJECT-TYPE
      SYNTAX  SEQUENCE OF EmergencyModeEntry
      ACCESS  not-accessible
      STATUS  current
      DESCRIPTION
              "Table of Emergency Mode."
      ::= { elecom 23 }

    ApWABEmergencyModeEntry OBJECT-TYPE
        SYNTAX  EmergencyModeEntry
        ACCESS  not-accessible
        STATUS  current
        DESCRIPTION
            "This OID configures the setting of Emergency Mode."
        INDEX   { EmergencyModeEnable }
        ::= { EmergencyModeTable 1 }

    EmergencyModeEntry ::=
      SEQUENCE {
          EmergencyModeEnable
              INTEGER,
          EmergencyWakeupEnable
              INTEGER
      }

    EmergencyModeEnable OBJECT-TYPE
        SYNTAX  INTEGER {
            Enable(1),
            Disable(2)
        }
        ACCESS  read-write
        DESCRIPTION
            "This OID configures Enable/Disable of Emergency Mode
        ::= { ApWABEmergencyModeEntry 1 }

    EmergencyWakeupEnable OBJECT-TYPE
        SYNTAX  INTEGER {
            Enable(1),
            Disable(2)
        }
        ACCESS  read-write
        DESCRIPTION
            "This OID configures Enable/Disable of Emergency Wakeup"
        ::= { ApWABEmergencyModeEntry 2 }

-- ========================================
-- Client
-- ========================================

	eleClientInfoTable   OBJECT-TYPE 
	  SYNTAX  SEQUENCE OF ClientInfoEntry
	  ACCESS  not-accessible
	  STATUS  current
	  DESCRIPTION
	          "Table of the connected stations."
	  ::= { elecom 1000 }

	eleApWABclientInfoEntry OBJECT-TYPE
		SYNTAX	ClientInfoEntry
		ACCESS	not-accessible
		STATUS	current
		DESCRIPTION
			"This OID indicates the information about connected clients.
			 (both of  wired and wireless ) "
		INDEX   { clientStaAddress }
		::= { eleClientInfoTable 1 }

	ClientInfoEntry ::=
	  SEQUENCE {
	      clientStaAddress
	          OCTET STRING,
	      clientStaSSID
	          OCTET STRING,
	      clientStaAuthType
	          OCTET STRING,
	      clientStaCliptType
	          OCTET STRING,
	      clientStaBand
	          INTEGER,
	      clientStaConnTime
	          TimeTicks,
	      clientStaConnTimeStamp
	          OCTET STRING,
          clientStaIPAddress
              OCTET STRING,
	  }

	clientStaAddress OBJECT-TYPE
		SYNTAX  OCTET STRING
		ACCESS  read-only
		STATUS  mandatory
		DESCRIPTION
			"This OID indicates the list the MAC address of the connected clients.
			 (both of  wired and wireless ) "
		::= { eleApWABclientInfoEntry 1 }

	clientStaSSID OBJECT-TYPE
		SYNTAX  OCTET STRING
		ACCESS  read-only
		STATUS  mandatory
		DESCRIPTION
			"This OID indicates the name of SSID that the STA was connected."
		::= { eleApWABclientInfoEntry 2 }

	clientStaAuthType OBJECT-TYPE
		SYNTAX  OCTET STRING
		ACCESS  read-only
		STATUS  mandatory
		DESCRIPTION
			"This OID indicates the Authentification type."
		::= { eleApWABclientInfoEntry 3 }

	clientStaCliptType OBJECT-TYPE
		SYNTAX  OCTET STRING
		ACCESS  read-only
		STATUS  mandatory
		DESCRIPTION
			"This OID indicates the clipt type."
		::= { eleApWABclientInfoEntry 4 }

	clientStaBand OBJECT-TYPE
		SYNTAX	INTEGER {
			wired(0),
			band_2_4GHz(2),
			band_5GHz(5)
		}
		ACCESS  read-only
		STATUS  mandatory
		DESCRIPTION
			"This OID indicates connected bandwidth of the STA."
		::= { eleApWABclientInfoEntry 5 }

	clientStaConnTime OBJECT-TYPE
		SYNTAX  TimeTicks
		ACCESS  read-only
		STATUS  mandatory
		DESCRIPTION
			"This OID indicates the connection time of the STA."
		::= { eleApWABclientInfoEntry 6 }

	clientStaConnTimeStamp OBJECT-TYPE
		SYNTAX  OCTET STRING
		ACCESS  read-only
		STATUS  mandatory
		DESCRIPTION
			"This OID indicates the connected time stamp of the STA."
		::= { eleApWABclientInfoEntry 7 }

    clientStaIPAddress OBJECT-TYPE
        SYNTAX  OCTET STRING
        ACCESS  read-only
		STATUS  mandatory
        DESCRIPTION
			"This OID indicates the IP address of the STA."
        ::= { eleApWABclientInfoEntry 8 }


-- ========================================
-- SSID information
-- ========================================

		ssidConfigTable OBJECT-TYPE
		  SYNTAX  SEQUENCE OF ClientSSIDInfoEntry
		  ACCESS  not-accessible
		  STATUS  mandatory
		  DESCRIPTION
		          "The OID table is describe about the each of SSID."
		  ::= { elecom 1010 }

		eleApWABSSIDConfigTable OBJECT-TYPE
			SYNTAX	ClientSSIDInfoEntry
			ACCESS	not-accessible
			STATUS	mandatory
			DESCRIPTION
		          "The OID table is describe about the each of SSID."
			INDEX   { ssidName }
			::= { ssidConfigTable 1 }


		ClientSSIDInfoEntry ::=
		  SEQUENCE {
		      ssidName
		          OCTET STRING,
		      ssidBandIndex
		          INTEGER,
		      ssidAuthType
		          INTEGER,
		      ssidAuthKeyLength
		          INTEGER,
		      ssidWEPKeyType
		          INTEGER,
		      ssidWEPKey
		          OCTET STRING,
		      ssidWPAType
		          INTEGER,
		      ssidWPAAuthType
		          INTEGER,
		      ssidWPAPreSharedKeyType
		          INTEGER,
		      ssidWPAPreSharedKey
		          OCTET STRING,
		      ssidAdditionalAuth
		          INTEGER,
		      ssidBroadCast
		          INTEGER,
		      ssidSeparater
		          INTEGER,
              ssidMacRadiusPwdType
                  INTEGER,
              ssidMacRadiusPwd
                  INTEGER,
		  }

		ssidName OBJECT-TYPE
			SYNTAX  OCTET STRING
			ACCESS  read-write
			STATUS  mandatory
			DESCRIPTION
				"This OID is the name of the SSID."
			::= { eleApWABSSIDConfigTable 1 }

		ssidBandIndex OBJECT-TYPE
			SYNTAX	INTEGER
			ACCESS  read-only
			STATUS  mandatory
			DESCRIPTION
				"Index value of each of band."
			::= { eleApWABSSIDConfigTable 2 }

		ssidAuthType OBJECT-TYPE
			SYNTAX	INTEGER {
				no_authentification(1),
				wep(2),
				wpa-psk(3),
				wpa-eap(4),
				ieee802_1x_eap(5)
			}
			ACCESS  read-write
			STATUS  mandatory
			DESCRIPTION
				"This OID is configuration about type of authentification.
				[1]No_Authentification
				[2]WEP
				[3]WPA-PSK
				[4]WPA-EAP
				[5]IEEE802_1x_EAP
				"
			::= { eleApWABSSIDConfigTable 3 }

		ssidAuthKeyLength OBJECT-TYPE
			SYNTAX	INTEGER {
				length_64bit(1),
				length_128bit(2)
			}
			ACCESS  read-write
			STATUS  mandatory
			DESCRIPTION
				" This OID is configuration about Key Length of WEP authentification.
				  This OID is available when ssidAuthType was WEP. 
				[1]64bit
				[2]128bit
				"
			::= { eleApWABSSIDConfigTable 4 }
		
		ssidWEPKeyType OBJECT-TYPE
			SYNTAX	INTEGER {
				ascii(1),
				hex(2)
			}
			ACCESS  read-write
			STATUS  mandatory
			DESCRIPTION
				" This OID is configuration about Key Type of WEP.
				  This OID is available when ssidAuthType was WEP. 
				[1]ascii
				[2]hex
				"
			::= { eleApWABSSIDConfigTable 5 }

		ssidWEPKey OBJECT-TYPE
			SYNTAX	OCTET STRING
			ACCESS  write-only
			STATUS  mandatory
			DESCRIPTION
				" This OID is configuration of WEP Key.
				  This OID is available when ssidAuthType was WEP. "
			::= { eleApWABSSIDConfigTable 6 }


		ssidWPAType OBJECT-TYPE
			SYNTAX	INTEGER {
				wpa_Disable(0),
				wpa-EAP(1),
				wpa2-eap(2),
				wpa2_mixed_mode-EAP(3),
				wpa_only(4),
				wpa2_only(5),
				wpa2_mixed_mode-PSK(6)
			}
			ACCESS  read-write
			STATUS  mandatory
			DESCRIPTION
				" This OID is configuration of WEP Key.
				  This OID is available when ssidAuthType was WPA-PSK or WPA-EAP.
				[0]WPA_Disable
				[1]WPA-EAP
				[2]WPA2-EAP
				[3]WPA2_mixed_mode-EAP
				[4]WPA_only
				[5]WPA2 only
				[6]WPA2_mixed_mode-PSK
				"
			::= { eleApWABSSIDConfigTable 7 }


		ssidWPAAuthType OBJECT-TYPE
			SYNTAX	INTEGER {
				wpa_Disable(0),
				aes(1),
				tkip(2),
				aes_mixed_mode(3)
			}
			ACCESS  read-write
			STATUS  mandatory
			DESCRIPTION
				"This OID is configuration about type of authentification for WPA.
				  This OID is available when ssidAuthType was WPA-PSK or WPA-EAP.
				[0] WPA_Disable
				[1] AES
				[2] TKIP
				[3] AES_mixed_mode
				"
				
			::= { eleApWABSSIDConfigTable 8 }

		ssidWPAPreSharedKeyType OBJECT-TYPE
			SYNTAX	INTEGER {
				pathphrase(1),
				hex(2)
			}
			ACCESS  read-write
			STATUS  mandatory
			DESCRIPTION
				"This OID is configuration about preshared key type of WPA.
				  This OID is available when ssidAuthType was WPA-PSK or WPA-EAP.
				[1] Path Phrase
				[2] HEX
				"
			::= { eleApWABSSIDConfigTable 9 }


		ssidWPAPreSharedKey OBJECT-TYPE
			SYNTAX	OCTET STRING
			ACCESS  write-only
			STATUS  mandatory
			DESCRIPTION
				"This OID is configuration about preshared key of WPA.
				  This OID is available when ssidAuthType was WPA-PSK or WPA-EAP.
				  "
			::= { eleApWABSSIDConfigTable 10 }


		ssidAdditionalAuth OBJECT-TYPE
			SYNTAX	INTEGER {
				no_additional_auth(1),
				mac_filter(2),
				mac_filter_and_macRadiusAuth(3),
				mac_radius_auth(4)
			}
			ACCESS  read-write
			STATUS  mandatory
			DESCRIPTION
				"This OID is configuration about addtional authentification.
				[1] No Additional Auth
				[2] MacFilter
				[3] MacFilter and MacRadiusAuth
				[4] MacRadiusAuth
				"
			::= { eleApWABSSIDConfigTable 11 }

		ssidBroadCast OBJECT-TYPE
			SYNTAX	INTEGER {
				disable(1),
				enable(2)
			}
			ACCESS  read-write
			STATUS  mandatory
			DESCRIPTION
				"This OID is configuration of SSID broadcasting.
				[1] Disable(stealth)
				[2] Enable
				"
			::= { eleApWABSSIDConfigTable 12 }


		ssidSeparater OBJECT-TYPE
			SYNTAX	INTEGER {
				disable(1),
				sta_Separater(2),
				ssid_Separater(3)
			}
			ACCESS  read-write
			STATUS  mandatory
			DESCRIPTION
				"This OID is configuration of SSID separater.
				[1] Disable
				[2] STA Separater
				[3] SSID Separater
			"
			::= { eleApWABSSIDConfigTable 13 }

        ssidMacRadiusPwdType OBJECT-TYPE
            SYNTAX  INTEGER {
                Use MAC address(1),
                Use the following password(2)
            }
            ACCESS  read-write
            STATUS  mandatory
            DESCRIPTION
                "This OID is configuration of SSID Mac RADIUS Password Type.
                [1] Use MAC address
                [2] Use the following password
            "
            ::= { eleApWABSSIDConfigTable 14 }

        ssidMacRadiusPwd OBJECT-TYPE
            SYNTAX  OCTET STRING
            ACCESS  write-only
            STATUS  mandatory
            DESCRIPTION
                "This OID is configuration of SSID Mac RADIUS Password."
            ::= { eleApWABSSIDConfigTable 15 }

-- ========================================
-- Wireless configuration
-- ========================================

	wirelessConfigTable OBJECT-TYPE
	  SYNTAX  SEQUENCE OF WirelessConfigEntry
	  ACCESS  not-accessible
	  STATUS  mandatory
	  DESCRIPTION
	          ""
	  ::= { elecom 1020 }


		eleApWABwirelessConfigTable OBJECT-TYPE
			SYNTAX	WirelessConfigEntry
			ACCESS	not-accessible
			STATUS	mandatory
			DESCRIPTION
				""
			INDEX   { wireless }
			::= { wirelessConfigTable 1 }


		WirelessConfigEntry ::=
		  SEQUENCE {
		      wireless
		          INTEGER,
		      wiressMode
		          INTEGER,
		      autoChannel 
		          INTEGER,
		      channel
		          INTEGER,
		      autoChannelRange
		          INTEGER,
		      channelBandwidth
		          INTEGER,
		      bss-BasicRateSet
		          INTEGER,
		      txPower
		          INTEGER,
              SSIDNumber
                  INTEGER
		  }
		
		wireless OBJECT-TYPE
			SYNTAX INTEGER {
				enable(1),
				disable(2)
			}
			ACCESS  read-write
			STATUS  mandatory
			DESCRIPTION
				"This OID configres the Enable _ Disaable the Wireless output."
			::= { eleApWABwirelessConfigTable 1 }

		wiressMode OBJECT-TYPE
			SYNTAX INTEGER {
				disable(0),
				b(1),
				g(2),
				b_g(3),
				g_n(4),
				b_g_n(5),
				a(6),
				a_n(7),
				a_n_ac(8)
			}
			ACCESS  read-write
			STATUS  mandatory
			DESCRIPTION
				"This OID configres the specification of WiFi.
				 To configure the OID, Enable the OID of Wireless.
					[1] 11b
					[2] 11g
					[3] 11b_g
					[4] 11g_n
					[5] 11b_g_n
					[6] 11a
					[7] 11a_n
					[8] 11a_n_ac
				 "
			::= { eleApWABwirelessConfigTable 2 }

		autoChannel OBJECT-TYPE
			SYNTAX INTEGER {
				enable(1),
				disable(2)
			}
			ACCESS  read-write
			STATUS  mandatory
			DESCRIPTION
				""
			::= { eleApWABwirelessConfigTable 3 }

		channel OBJECT-TYPE
			SYNTAX INTEGER
			ACCESS  read-write
			STATUS  mandatory
			DESCRIPTION
				"This OID configres the channel.
				 To configure the OID, Disable the OID of AutoChannel.
				 (2.4GHz)
				 	1,2,3,4,5,6,7,8,9,10,11,12,13
				 (5GHz)
				 	36,40,44,48,52,56,60,64,100,104,108,112,116,120,124,128,132,136,140"
			::= { eleApWABwirelessConfigTable 4 }


		autoChannelRange OBJECT-TYPE
			SYNTAX INTEGER {
				disable(0),
				ch1-11(1),
				ch1-13(2),
				w52(3),
				w52_w53(4),
				w52_w53_w56(5)
			}
			ACCESS  read-write
			STATUS  mandatory
			DESCRIPTION
				"This parameter is configration of enable _ disable AutoChannel and selection of bandwidth.
				 please specify from below. 
				(Disable AutoChannel)
				  [0] Disable
				(Enable AutoChannel)
				  (11b, 11g, 11b_g, 11b_n, 11b_g_n)
				    [1] ch1-11
				    [2] ch1-13
				  (11a, 11a_n, 11a_n_ac)
					[3]W52
					[4]W52_W53
					[5]W52_W53_W56
					"
			::= { eleApWABwirelessConfigTable 5 }

		channelBandwidth OBJECT-TYPE
			SYNTAX INTEGER {
				disable(0),
				band_20MHz(1),
				band_40MHz(2),
				auto(3),
				band_40MHz_plus_Next_Ch(4),
				band_40MHz_plus_Prev_Ch(5),
				auto_plus_Next_Ch(6),
				auto_plus_Prev_Ch(7),
				auto80_40_20MHz(8)
			}
			ACCESS  read-write
			STATUS  mandatory
			DESCRIPTION
				"This parameter is configration of ChannelBandwidth .
				 ChannelBandwidth configures about band width for channel.
				 This parameter is selectable. please specify from below. 
				(11b, 11g, 11b_g)
				  <AutoChannel On_Off>
					[1] 20MHz
				(11b_n, 11b_g_n)
				  <AutoChannel On>
					[1] 20MHz
					[2] 40MHz
					[3] Auto
				  <AutoChannel Off (ch 1,2,3,4)  >
					[1] 20MHz
					[5] 40MHz + previous ch
					[7] Auto  + previous ch
				  <AutoChannel Off (ch 5,6,7,8,9) >
					[1] 20MHz
					[4] 40MHz + next ch
					[5] 40MHz + previous ch
					[6] Auto + next ch
					[7] Auto + previous ch
				  <AutoChannel Off (ch 10,11,12,13) >
					[1] 20MHz
					[4] 40MHz + next ch
					[6] Auto + next ch
				(11a)
				  <AutoChannel On_Off>
					[1] 20MHz
				(11a_n)
				  <AutoChannel On>
					[1] 20MHz
					[2] 40MHz
				  <AutoChannel Off (ch 36, 44, 52, 60, 100, 108, 116, 124, 132) >
					[1] 20MHz
					[5] 40MHz + previous ch
				  <AutoChannel Off (ch 40, 48, 56, 64, 104, 112, 120, 128, 136) >
					[1] 20MHz
					[6] Auto + next ch
				(11a_n_ac)
				  <AutoChannel On>
					[1] 20MHz
					[8] Auto 80_40_20MHz
				  <AutoChannel Off (ch 36, 44, 52, 60, 100, 108, 116, 124) >
					[1] 20MHz
					[5] 40MHz + previous ch
					[8] Auto 80_40_20MHz
				  <AutoChannel Off (ch 40, 48, 56, 64, 104, 112, 120, 128) >
					[1] 20MHz
					[4] 40MHz + next ch
					[8] Auto 80_40_20MHz
				  <AutoChannel Off (ch 132) >
					[1] 20MHz
					[5] 40MHz + previous ch
				  <AutoChannel Off (ch 136)>
					[1] 20MHz
					[4] 40MHz + next ch
				  <AutoChannel Off (ch 140)>
					[1] 20MHz   "
				 
			::= { eleApWABwirelessConfigTable 6 }

		bss-BasicRateSet OBJECT-TYPE
			SYNTAX INTEGER {
				disable(0),
				bss_1_2_Mbps(1),
				bss_1_2_5-5_11Mbps_or_all(2),
				bss_1_2_5-5_6_11_12_24Mbps(3),
				bss_6_12_24Mbps(4),
				all(5)
			}
			ACCESS  read-write
			STATUS  mandatory
			DESCRIPTION
				"This parameter is configration of BasicRateSet.
				 BasicRateSet is configration of communication speed. 
				 select the transmission speed of from below.
				 (for 2.4MHz : 11b)  
				 [0] : Disable
				 [1] : 1,2Mbps
				 [2] : all
				 
				 (for 2.4MHz : 11b)  
				 [0] : Disable
				 [1] : 1,2Mbps
				 [2] : 1,2,5.5,11Mbps
				 [3] : 1,2,5.5,6,11,12,24Mbps
				 [5] : all
				 
				 (for 5MHz)
				 [0] : Disable
				 [4] : 6,12,24Mbp
				 [5] : all"
			::= { eleApWABwirelessConfigTable 7 }

		txPower OBJECT-TYPE
			SYNTAX INTEGER {
				disable(0),
				tx_10_percent(10),
				tx_25_percent(25),
				tx_50_percent(50),
				tx_75_percent(75),
				tx_90_percent(90),
				tx_100_percent(100)
			}
			ACCESS  read-write
			STATUS  mandatory
			DESCRIPTION
				"This parameter is configration of Tx power of radio wave.
				 Tx power configures radio wave intensity of transmit power.
				 This parameter is selectable. please specify from below. 
				 [100]100%
				 [90]90%
				 [75]75%
				 [50]50%
				 [25]25%
				 [10]10%
				 [0] Disable"
			::= { eleApWABwirelessConfigTable 8 }
        SSIDNumber OBJECT-TYPE
            SYNTAX INTEGER
            ACCESS  read-write
            STATUS  mandatory
            DESCRIPTION
                "This OID configres the number of SSID.
                 This parameter is selectable. please specify from below.
                    1,2,3,4,5,6,7,8,9,10,11,12,13,14,15,16"
            ::= { eleApWABwirelessConfigTable 9 }

END
